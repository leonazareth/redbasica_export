Attribute VB_Name = "frmColetor"
Attribute VB_Base = "0{07AA3F90-D2CE-4F05-947C-ED919A0C2B98}{B170BB15-2BE7-45A0-B8C8-A6D1E3C344D7}"
Attribute VB_GlobalNameSpace = False
Attribute VB_Creatable = False
Attribute VB_PredeclaredId = True
Attribute VB_Exposed = False
Attribute VB_TemplateDerived = False
Attribute VB_Customizable = False
Private Const caminho = "C:\UTFEsg\"
Private Const nameBlk = "BLOCO_TRAMO_INSERT"
Private Const pi As Double = 3.14159265358979
Private blockRefAltera As AcadBlockReference

Private Sub cmdAlterar_Click()
Dim oEnt As AcadEntity
Dim p As Variant

'Selecionar Bloco
Me.Hide
 ThisDrawing.Utility.GetEntity oEnt, p, "Selecione o Tramo"
Set blockRefAltera = oEnt
ObterDadosAtributosDoBloco blockRefAltera
cmdOK.Caption = "Gravar"
Me.show

End Sub
Private Function ObterDadosAtributosDoBloco(oBlk As AcadBlockReference) As String
Dim elem As Object
Dim item As Object
Dim Array1 As Variant
Dim count As Integer
Dim MBtest1 As String
Dim str As String
Dim intLin As Integer
Dim varAttribs As Variant
Dim intI As Integer
Dim parteE As String
Dim parteD As String
Dim trm As String


            If oBlk.HasAttributes Then
                varAttribs = oBlk.GetAttributes
                For intI = LBound(varAttribs) To UBound(varAttribs)
                 ReDim Preserve matrizAtributos(1, intLin)
                     matrizAtributos(0, intLin) = varAttribs(intI).TagString
                     matrizAtributos(1, intLin) = varAttribs(intI).TextString
                        If varAttribs(intI).TagString = "TRM" Then
                            trm = varAttribs(intI).TextString
                            parteE = Replace(RetornaParteDeUmaString(trm, "-", True), "-", "")
                            parteD = Replace(RetornaParteDeUmaString(trm, "-", False), "-", "")
                            txtNrColetor.Text = parteE
                            txtNrTrecho.Text = parteD
                        ElseIf varAttribs(intI).TagString = "COTAT" Then
                            txtCotat.Text = varAttribs(intI).TextString
                        ElseIf varAttribs(intI).TagString = "QE" Then
                            txtQE.Text = varAttribs(intI).TextString
                        End If
                Next
            End If
            linhaAtributo = intLin

End Function
Private Sub cmdCancelar_Click()
cmdOK.Caption = "OK"
Me.Hide
End Sub

Private Sub cmdIniciarColetor_Click()
Dim nrColetor As Integer

'Obtém o número do coletor que parou e incrementa
If txtNrColetor = "" Then txtNrColetor = 0
nrColetor = txtNrColetor
txtNrColetor = nrColetor + 1
txtNrTrecho = 1

End Sub
Private Sub cmdOK_Click()
    Dim returnPnt As Variant
    Dim objBlk As AcadBlockReference
    Dim iAngle As Double
    Dim strObjtInsert As String
    Dim p1 As Variant
    Dim p2 As Variant
    Dim dist As Double
    Dim result As Variant
    Dim trecho As String
    Dim coletor As String
    On Error GoTo cmdOK_Click_Error
 
 Me.Hide 'Esconde o formulário
 
 If cmdOK.Caption = "Gravar" Then
    inserirAtributoColetorETramo txtNrTrecho, txtNrColetor, blockRefAltera, txtCotat.Text, txtQE.Text
    cmdOK.Caption = "OK"
    LimparForm
    Exit Sub
 End If
 
 If txtNrTrecho = "" Then txtNrTrecho = 1
 
'Verificar se tem dados no formulário
 If txtNrColetor.Text = "" Then 'Verifica dados no campo Número coletor
    MsgBox "Falta número do coletor"
    txtNrColetor.SetFocus
 End If
 
 If txtNrTrecho = "" Then 'Verificando se tem dados no campo trecho
    MsgBox "Falta número do trecho"
    txtNrTrecho.SetFocus
 End If
 
 If txtCotat.Text = "" Then 'Verificando se tem dados no Conta Terreno
    MsgBox "Falta Cota do Terreno"
    txtCotat.SetFocus
 End If
 
  If txtQE.Text = "" Then 'Verificando se tem dados Nr Unidades
    MsgBox "Falta Nr Unidades"
    txtQE.SetFocus
 End If
 
 
 trecho = txtNrTrecho.Text
 coletor = txtNrColetor.Text
 
 'Modifica Numeração trecho
If Len(txtNrTrecho.Text) = "1" Then
    trecho = "00" & trecho
ElseIf Len(txtNrTrecho.Text) = 2 Then
    trecho = "0" & trecho
End If
 
 'Modifica Numeração coletor
If Len(txtNrColetor.Text) = 1 Then
    coletor = "00" & coletor
ElseIf Len(txtNrColetor.Text) = 2 Then
    coletor = "0" & coletor
End If
 
 
 '# Verifica se coletor e número do trecho já existe
If chkVerifica.value = True Then
 If TramoExiste(coletor & "-" & trecho) = True Then
    result = MsgBox("Tramo já existe, Deseja Inserir?", vbYesNo, "Inserir Tramo")
    If result = vbNo Then
        Exit Sub
    End If
 End If
End If
 
 
'Obter um ponto
 p1 = ThisDrawing.Utility.GetPoint(, "Escolha 1º Ponto: ")
 p2 = ThisDrawing.Utility.GetPoint(p1, "Escolha 2º Ponto: ")
 
Dim d As Double
d = ThisDrawing.Utility.AngleFromXAxis(p1, p2)
dist = DistancePoint(p1, p2)

'Inserir Objeto bloco
ThisDrawing.ActiveSpace = acModelSpace
'iAngle = ThisDrawing.Utility.GetAngle(returnPnt, "Selecione o ângulo de rotação: ")

Set objBlk = ActiveDocument.ModelSpace.InsertBlock(p1, caminho & "\" & nameBlk & ".dwg", 1#, 1#, 1#, 0)
objBlk.Update

 'Explodindo objetos para ficar dinâmico
ThisDrawing.SendCommand "_EXPLODE" & vbCr & SendCommandSelection(objBlk) & vbCr & vbCr

Dim ent As AcadEntity
Dim oBkRef As IAcadBlockReference
Set oBkRef = LastEntity(ThisDrawing.ModelSpace)
 
'Inserir o Coletor e Tramo no Bloco
inserirAtributoColetorETramo trecho, coletor, oBkRef, txtCotat.Text, txtQE.Text

'Modificar Distancia
ModifyProperty "Distance1", dist, oBkRef
oBkRef.Update

    If Round(p2(0), 4) = Round(p1(0), 4) Then
        If oBkRef.IsDynamicBlock Then
            oProps = oBkRef.GetDynamicBlockProperties
            For i = 0 To UBound(oProps)
                Set oDblkProp = oProps(i)
                If oDblkProp.PropertyName = "Angle1" Then
                        oDblkProp.value = d
                        oBkRef.Update
                End If
            Next
        End If
    ElseIf p2(0) < p1(0) Then 'Modifica Flip
        If oBkRef.IsDynamicBlock Then
            oProps = oBkRef.GetDynamicBlockProperties
            For i = 0 To UBound(oProps)
                Set oDblkProp = oProps(i)
                'Debug.Print oDblkProp.PropertyName
                If oDblkProp.PropertyName = "Flip state1" Then
                    oDblkProp.value = 1
                End If
                If oDblkProp.PropertyName = "Flip state2" Then
                    oDblkProp.value = 1
                End If
            Next
        End If
            oBkRef.Update
    
        If oBkRef.IsDynamicBlock Then
            oProps = oBkRef.GetDynamicBlockProperties
            For i = 0 To UBound(oProps)
                Set oDblkProp = oProps(i)
                If oDblkProp.PropertyName = "Angle1" Then
                    If d > 2 Then
                        d = d - pi
                        oDblkProp.value = -d
                    Else
                        oDblkProp.value = d
                    End If
                       
                        oBkRef.Update
                End If
            Next
        End If
    Else
     oBkRef.Update
    'Modifica angulo
        If oBkRef.IsDynamicBlock Then
            oProps = oBkRef.GetDynamicBlockProperties
            For i = 0 To UBound(oProps)
                Set oDblkProp = oProps(i)
                If oDblkProp.PropertyName = "Angle1" Then
                        oDblkProp.value = d
                        oBkRef.Update
                End If
            Next
        End If
    End If
    
     oBkRef.Update
   
'Persistir os dados no formulário
txtNrTrecho.Text = txtNrTrecho.Text + 1
ThisDrawing.Regen (acActiveViewport)
Me.show
  Exit Sub
cmdOK_Click_Error:
     If Err.Number = -2147352567 Then
        Exit Sub
    Else
        MsgBox Err.Description, vbInformation, "Coletor"
        Exit Sub
    End If
End Sub
Private Function inserirAtributoColetorETramo(strTramo As String, strColetor As String, oBlk As AcadBlockReference, cotat As String, qe As String)
Dim varAttribs As Variant
Dim intI As Integer
Dim Strcomando As String

    varAttribs = oBlk.GetAttributes
        For intI = LBound(varAttribs) To UBound(varAttribs)
            If varAttribs(intI).TagString = "TRM" Then
                    varAttribs(intI).TextString = strColetor & "-" & strTramo
            ElseIf varAttribs(intI).TagString = "COTAT" Then
                    varAttribs(intI).TextString = cotat
            ElseIf varAttribs(intI).TagString = "QE" Then
                    varAttribs(intI).TextString = qe
            End If
        Next

End Function
Function SendCommandSelection(ent As AcadEntity) As String
   SendCommandSelection = "(handent " & Chr(34) & ent.Handle & Chr(34) & ")"
End Function
Public Function LastEntity(container As AcadBlock) As AcadEntity
    Set LastEntity = container(container.count - 1)
End Function
Private Sub LimparForm()
    txtNrColetor.Text = ""
    txtNrTrecho.Text = ""
    txtCotat.Text = ""
    txtQE.Text = ""
End Sub


Private Sub lblNrUnidade_Click()

End Sub

Attribute VB_Name = "frmExportarImportarDados"
Attribute VB_Base = "0{25E42A75-3A18-408A-A46D-40A9A88E35FE}{943F90EC-5FE0-41C3-BAC6-1F2AA9329570}"
Attribute VB_GlobalNameSpace = False
Attribute VB_Creatable = False
Attribute VB_PredeclaredId = True
Attribute VB_Exposed = False
Attribute VB_TemplateDerived = False
Attribute VB_Customizable = False
Private Sub Filepath_Click()
txtPath.Text = getFiled(txtPath.Text, "xlsm", "Excel")
End Sub
Private Sub cmdExportar_Click()
Dim trecho As Variant
Dim trechox As String
Dim coletor As Variant
Dim coletorx As String
Dim strTrecho As String
Dim oBlkRef As AcadBlockReference
Dim oBlkRefPoint As AcadBlockReference
Dim oEnt As AcadEntity
Dim minExt As Variant
Dim maxExt As Variant
Dim objMatrizEntidade() As AcadBlockReference
Dim objMatrizEntidade2() As AcadBlockReference
Dim objMatrizTramo() As String
Dim objMatrizTramoNum() As Integer
Dim objMatrizTramoNum2() As Integer
'Dim matrizAtributos() As String
Dim i As Integer
Dim z As Integer
Dim q As Integer
Dim m As Integer
Dim linha As Integer
Dim linhaPonto As Integer
Dim trm As String
Dim encontrou As Boolean
Dim arquivo As String
 On Error GoTo cmdExportar_Click_Err
linha = 2
linhaPonto = 2
 
'Verifica caminho
If txtPath.Text = "" Then
    MsgBox "Por favor indicar um arquivo", vbInformation, "Exportar"
    txtPath.SetFocus
End If


'Nome Arquivo
arquivo = RetornaParteDeUmaString(txtPath.Text, "\", False)
arquivo = Replace(arquivo, "\", "")

'Conectar com excel
ExcelConnect txtPath.Text, arquivo, "Dados importados"

'Buscar por trechos
For coletor = 1 To 100
        For trecho = 1 To 1000
        
         'Modifica Numeração trecho
            If Len(trecho) = 1 Then
                trechox = "00" & trecho
            ElseIf Len(trecho) = 2 Then
                trechox = "0" & trecho
            End If
             
             'Modifica Numeração coletor
            If Len(coletor) = 1 Then
                coletorx = "00" & coletor
            ElseIf Len(coletor) = 2 Then
                coletorx = "0" & coletor
            End If
              
        strTrecho = coletorx & "-" & trechox
        Set oBlkRef = EncontrarBlocoPeloTextAtributo(strTrecho) 'Obter o bloco com o trecho
        'Gravar Atributos do ponto  na planilha
        If Not oBlkRef Is Nothing Then
            encontrou = True
            Set oEnt = oBlkRef
            ZoomTotalObjeto oEnt 'Zoom no objeto
            Erase matrizAtributos
            ObterAtributosDoBloco oBlkRef 'Obter os  atributos do bloco
            RegistraAtributoNaPlanilha oBlkRef.ObjectID, linha   'Registrar na planilha
            linhaPonto = linha
            linha = linha + 1
            
            'Obter blocos do ponto
            'oBlkRef.GetBoundingBox minExt, maxExt
            Erase objMatrizEntidade
            ObterBlocosNoPonto oBlkRef.InsertionPoint, oBlkRef.InsertionPoint, objMatrizEntidade
            
            'Ler Matriz
            i = UBound(objMatrizEntidade)
            Dim colunTramo As Integer
            colunTramo = 0
            qtdTramo = 0
            For z = 0 To i
               Set oBlkRefPoint = objMatrizEntidade(z)
               If objMatrizEntidade(z).Handle = oBlkRef.Handle Then
                    If colunTramo <> 0 Then
                        colunTramo = colunTramo - 1
                    End If
               Else
                trm = ObterAtributosDoBloco(oBlkRefPoint)
                trecho_y = Replace(RetornaParteDeUmaString(trm, "-", False), "-", "")
                    'Gravar na linha do ponto o nome do trecho
                    If trm <> coletor & "-" & trecho Then
                        'Registar apenas se tem sequência
                        'RegistraTrmNoPonto trm, 6 + colunTramo, linhaPonto 'Registrar na planilha
                        ReDim Preserve objMatrizTramo(qtdTramo) As String
                        ReDim Preserve objMatrizTramoNum(qtdTramo) As Integer
                        objMatrizTramo(qtdTramo) = trm
                        objMatrizTramoNum(qtdTramo) = Replace(RetornaParteDeUmaString(trm, "-", True), "-", "")
                        qtdTramo = qtdTramo + 1
                    End If
                End If
            Next z
        Else
            Exit For
        End If
        
           'verifica se tem trechos
                 Dim qtdTrechos As Integer
                 Dim trechoAtual As Integer
                 
                 If trm <> "" Then
                    objMatrizTramoNum2 = BubbleSrt(objMatrizTramoNum, True)
                    qtdTrechos = UBound(objMatrizTramoNum2)
                        For n = 0 To qtdTrechos
                           For p = 0 To qtdTrechos
                             trechoAtual = Replace(RetornaParteDeUmaString(objMatrizTramo(p), "-", True), "-", "")
                             If trechoAtual = objMatrizTramoNum(n) Then
                                If colunTramo <= 2 Then
                                    RegistraTrmNoPonto objMatrizTramo(p), 6 + colunTramo, linhaPonto 'Registrar na planilha
                                    colunTramo = colunTramo + 1
                               End If
                             End If
                           Next p
                        Next n
                 End If
                 Set oBlkRefPoint = Nothing
                 Erase objMatrizTramo
                 Erase objMatrizTramoNum
                 Erase objMatrizTramoNum2
                 trm = ""
    Next trecho
Next coletor


ThisDrawing.Regen (acActiveViewport)

If encontrou = False Then
    MsgBox "Não foi encontrado Coletores no range de 1 à 1000", vbInformation, "Exportar"
End If

'ExcelClose
SheetSave

'Limpar Matrizes
Erase matrizAtributos
Erase objMatrizEntidade

MsgBox "Exportação terminou", vbInformation, "Exportação excel"
Exit Sub

cmdExportar_Click_Err:
MsgBox "Erro no Módulo cmdExportar_Click_Err: " & Err.Description, vbInformation, "Exportação excel"
End Sub
Private Sub cmdImportar_Click()
Dim linha As Integer
Dim z As Integer
Dim i As Integer
Dim q As Integer
Dim id As LongLong
Dim qtdLinhas As Integer
Dim qtdColunas As Integer
Dim arquivo As String
Dim oBlkRef As AcadBlockReference
On Error GoTo cmdImportar_Click_Err

linha = 2

'Verifica se o caminho é válido
If txtPath.Text = "" Then
    MsgBox "Escolha um caminho válido", vbInformation, "Importar Dados Excel"
    Exit Sub
End If

'Nome Arquivo
arquivo = RetornaParteDeUmaString(txtPath.Text, "\", False)
arquivo = Replace(arquivo, "\", "")

'Conectar com excel
ExcelConnect txtPath.Text, arquivo, "Dados exportados"

'Obter quantidade de linhas e colunas preenchidas
qtdLinhas = SheetCountLinhas
qtdColunas = SheetCountColunas

'Ler linhas do excel
For z = 2 To qtdLinhas
    'Colocar dados Excel na Matriz
    Erase matrizDadosExcel
    ObterDadosDaPlanilha z, qtdColunas
    'Obter Bloco pelo Id
    If (matrizDadosExcel(1, 0)) = "" Then Exit For
    id = (matrizDadosExcel(1, 0))
    If id = 0 Then Exit For
    Set oBlkRef = ObterBlocosPeloId(id)
    'Colocar dados Excel no Bloco
    ColocarDadosNoBloco oBlkRef
Next z

ThisDrawing.Regen (acActiveViewport)

'Limpar Matrizes
Erase matrizDadosExcel

MsgBox "Importação Finalizada", vbInformation, "Importação Dados Excel"
Exit Sub

cmdImportar_Click_Err:
MsgBox "Erro na sub importar: " & Err.Description, vbInformation, "Importar da dos do excel"
ExcelClose
End Sub

Private Sub UserForm_Terminate()
''On Error GoTo UserForm_Terminate_Err
    ''ExcelClose
''UserForm_Terminate_Err:
''Exit Sub
End Sub
Private Sub cmdExportar2_Click()
Dim trecho As Variant
Dim coletor As Variant
Dim strTrecho As String
Dim oBlkRef As AcadBlockReference
Dim oBlkRefPoint As AcadBlockReference
Dim oEnt As AcadEntity
Dim minExt As Variant
Dim maxExt As Variant
Dim objMatrizEntidade() As AcadBlockReference
Dim objMatrizEntidade2() As AcadBlockReference
Dim objMatrizTramo() As String
Dim objMatrizTramoNum() As Integer
'Dim matrizAtributos() As String
Dim i As Integer
Dim z As Integer
Dim q As Integer
Dim m As Integer
Dim linha As Integer
Dim linhaPonto As Integer
Dim trm As String
Dim encontrou As Boolean
Dim arquivo As String
 On Error GoTo cmdExportar_Click_Err
linha = 2
linhaPonto = 2
 
'Verifica caminho
If txtPath.Text = "" Then
    MsgBox "Por favor indicar um arquivo", vbInformation, "Exportar"
    txtPath.SetFocus
End If


'Nome Arquivo
arquivo = RetornaParteDeUmaString(txtPath.Text, "\", False)
arquivo = Replace(arquivo, "\", "")

'Conectar com excel
ExcelConnect txtPath.Text, arquivo, "Dados importados"

'Buscar por trechos
For coletor = 1 To 100
        For trecho = 1 To 1000
        strTrecho = coletor & "-" & trecho
        Set oBlkRef = EncontrarBlocoPeloTextAtributo(strTrecho) 'Obter o bloco com o trecho
        'Gravar Atributos do ponto  na planilha
        If Not oBlkRef Is Nothing Then
            encontrou = True
            Set oEnt = oBlkRef
            ZoomTotalObjeto oEnt 'Zoom no objeto
            Erase matrizAtributos
            ObterAtributosDoBloco oBlkRef 'Obter os  atributos do bloco
            RegistraAtributoNaPlanilha oBlkRef.ObjectID, linha   'Registrar na planilha
            linhaPonto = linha
            linha = linha + 1
            
            'Obter blocos do ponto
            'oBlkRef.GetBoundingBox minExt, maxExt
            Erase objMatrizEntidade
            ObterBlocosNoPonto oBlkRef.InsertionPoint, oBlkRef.InsertionPoint, objMatrizEntidade
            
            'Ler Matriz
            i = UBound(objMatrizEntidade)
            Dim colunTramo As Integer
            colunTramo = 0
            
            For z = 0 To i
               Set oBlkRefPoint = objMatrizEntidade(z)
               
               If objMatrizEntidade(z).Handle = oBlkRef.Handle Then
                    If colunTramo <> 0 Then
                        colunTramo = colunTramo - 1
                    End If
               Else
                'Gravar os atributos do trecho na planilha
                 'Verifica se existe tramo chegando até o ponto equanto houver siga
                 Dim encontrei As Boolean
                 Dim qtdNoPonto As Integer
                 Dim qtdTramo As Integer
                 Erase objMatrizTramo
                 
                 Set oBlkRefPoint = oBlkRef
                 qtdTramo = 0
                 encontrei = True
                 
                 While encontrei = True
                    ObterBlocosNoPonto oBlkRefPoint.InsertionPoint, oBlkRefPoint.InsertionPoint, objMatrizEntidade2
                    trm = ObterAtributosDoBloco(oBlkRefPoint)  'Obter os  atributos do bloco
                    qtdNoPonto = UBound(objMatrizEntidade2)
                        If qtdNoPonto > 0 Then
                            For m = 0 To qtdNoPonto
                                Dim trecho_y As String
                                Set oBlkRefPoint = objMatrizEntidade2(m)
                                trm = ObterAtributosDoBloco(oBlkRefPoint)
                                trecho_y = Replace(RetornaParteDeUmaString(trm, "-", False), "-", "")
                                'Gravar na linha do ponto o nome do trecho
                                If trm <> coletor & "-" & trecho Then
                                    Erase matrizAtributos
                                    'Registar apenas se tem sequência
                                    'RegistraTrmNoPonto trm, 6 + colunTramo, linhaPonto 'Registrar na planilha
                                    ReDim Preserve objMatrizTramo(qtdTramo) As String
                                    ReDim Preserve objMatrizTramoNum(qtdTramo) As Integer
                                    objMatrizTramo(qtdTramo) = trm
                                    objMatrizTramo(qtdTramo) = Replace(RetornaParteDeUmaString(trm, "-", True), "-", "")
                                    qtdTramo = qtdTramo + 1
                                                                   
                                    If m < qtdNoPonto Then
                                        Set oBlkRefPoint = objMatrizEntidade2(m + 1)
                                    Else
                                       encontrei = False
                                    End If
                                End If
AAA:
                            Next m
                        Else
                            encontrei = False
                        End If
                 Wend
                 
                 'verifica se tem trechos
                 Dim qtdTrechos As Integer
                 Dim trechoAtual As Integer
                 
                 qtdTrechos = UBound(objMatrizTramoNum)
   
                 For n = 0 To qtdTrechos
                    For p = 0 To qtdTrechos
                      trechoAtual = Replace(RetornaParteDeUmaString(trm, "-", True), "-", "")
                      If trechoAtual = objMatrizTramoNum(n) Then
                        RegistraTrmNoPonto trm, 6 + colunTramo, linhaPonto 'Registrar na planilha
                        colunTramo = colunTramo + 1
                      End If
                    Next p
                 Next n
                 
                End If
            Next z
        Else
            Exit For
        End If
    Next trecho
Next coletor


ThisDrawing.Regen (acActiveViewport)

If encontrou = False Then
    MsgBox "Não foi encontrado Coletores no range de 1 à 1000", vbInformation, "Exportar"
End If

'ExcelClose
SheetSave

'Limpar Matrizes
Erase matrizAtributos
Erase objMatrizEntidade

MsgBox "Exportação terminou", vbInformation, "Exportação excel"
Exit Sub

cmdExportar_Click_Err:
MsgBox "Erro no Módulo cmdExportar_Click_Err: " & Err.Description, vbInformation, "Exportação excel"
End Sub

Attribute VB_Name = "frmMenu"
Attribute VB_Base = "0{2E28F126-3DC3-4C8B-9417-E7C5576BF8CC}{91BB1F65-BF43-49CB-958E-C45ACDB06291}"
Attribute VB_GlobalNameSpace = False
Attribute VB_Creatable = False
Attribute VB_PredeclaredId = True
Attribute VB_Exposed = False
Attribute VB_TemplateDerived = False
Attribute VB_Customizable = False
Private Sub cmdExportarImprotar_Click()
Me.Hide
frmExportarImportarDados.show
End Sub

Private Sub cmdTramo_Click()
Me.Hide
frmColetor.show
End Sub

Private Sub Label17_Click()

End Sub

Attribute VB_Name = "mdl_ConexaoExcel"
Option Explicit
Dim xlapp As Excel.Application
Dim xlbook As Excel.Workbook
Dim xlsheet As Excel.Worksheet

Function ExcelConnect(caminho As String, arquivo As String, plan As String)
    'set referencia
    Set xlbook = GetObject(caminho)
    'set referencia workbook
    Set xlapp = xlbook.Parent
    'fazer Excel visible
    xlapp.Visible = True
    xlapp.Windows(arquivo).Visible = True
    Set xlsheet = xlbook.Sheets(plan)
End Function
Function ExcelClose()
    xlbook.Close savechanges:=True
    xlapp.Quit
    Set xlsheet = Nothing
    Set xlbook = Nothing
    Set xlapp = Nothing
End Function
Function GetCellValue(row As Integer, column As Integer) As Variant
' Esta função retorna o valor de uma célula do excel
GetCellValue = xlsheet.Cells(row, column)
End Function
Function SheetCountLinhas() As Integer
    SheetCountLinhas = xlsheet.UsedRange.Rows.count
End Function
Function SheetCountColunas() As Integer
    SheetCountColunas = xlsheet.UsedRange.Columns.count
End Function
Function SetCellValue(row As Integer, column As Integer, valor As String)
  xlsheet.Cells(row, column) = valor
End Function
Function LimparPlanilha()
    xlsheet.ClearArrows
End Function
Function SheetSave()
    xlbook.Save
End Function

Attribute VB_Name = "mdl_Exportar"
Global matrizAtributos() As String
Global linhaAtributo As Integer
Function ObterBlocosNoPonto(min As Variant, max As Variant, ByRef objMatrizEntidade)
Dim elem As Object
Dim oBlk As AcadBlockReference
Dim item As Object
Dim Array1 As Variant
Dim count As Integer
Dim MBtest1 As String
Dim str As String
Dim oSelect As AcadSelectionSet
Dim iFilterCode(0) As Integer
Dim vFilterValue(0) As Variant
Dim varAttribs As Variant
Dim intI As Integer
Dim intLin As Integer
Dim i As Integer
    linhaAtributo = 0
    intLin = 0
    iFilterCode(0) = 0
    vFilterValue(0) = "INSERT"

    'Excluir Seleções anteriores
    On Error Resume Next
    For i = 0 To ActiveDocument.SelectionSets.count - 1
        If ActiveDocument.SelectionSets.item(i).Name = "ObterBlocosNoPonto" Then
            ActiveDocument.SelectionSets.item(i).Delete
        End If
    Next i
    
    'Obter todas os bloco insert dentro do quadrado
    Set oSelect = ActiveDocument.SelectionSets.Add("ObterBlocosNoPonto")
    oSelect.Select acSelectionSetCrossing, min, max, iFilterCode, vFilterValue
    
    'Obter os blocos do ponto
    For Each elem In oSelect
        If elem.EntityName = "AcDbBlockReference" Then
            If elem.HasAttributes Then
                ReDim Preserve objMatrizEntidade(intLin) As AcadBlockReference
                Set oBlk = elem
                Set objMatrizEntidade(intLin) = oBlk
                intLin = intLin + 1
            End If
        End If
    Next
    linhaAtributo = intLin
End Function
Function ObterAtributosDoBloco(oBlk As AcadBlockReference) As String
Dim elem As Object
Dim item As Object
Dim Array1 As Variant
Dim count As Integer
Dim MBtest1 As String
Dim str As String
Dim intLin As Integer
Dim varAttribs As Variant
Dim intI As Integer

intLin = 0

            If oBlk.HasAttributes Then
                varAttribs = oBlk.GetAttributes
                For intI = LBound(varAttribs) To UBound(varAttribs)
                 ReDim Preserve matrizAtributos(1, intLin)
                     matrizAtributos(0, intLin) = varAttribs(intI).TagString
                     matrizAtributos(1, intLin) = varAttribs(intI).TextString
                        If varAttribs(intI).TagString = "TRM" Then
                            ObterAtributosDoBloco = varAttribs(intI).TextString
                        End If
                    intLin = intLin + 1
                Next
            End If
            linhaAtributo = intLin

End Function
Sub RegistraAtributoNaPlanilha(strIdBloco As String, linha As Integer)
Dim q As Integer
Dim m As Integer

m = linhaAtributo - 1
SetCellValue linha, 1, strIdBloco 'Registrando Id Bloco

 For q = 0 To m
    Select Case matrizAtributos(0, q)
        Case "PROFPV"
        Case "COTAF"
        Case "COTAT"
            SetCellValue linha, 3, matrizAtributos(1, q)
        Case "DIAM"
        Case "PROF2"
        Case "DECLIVIDADE"
        Case "EXT"
            SetCellValue linha, 4, matrizAtributos(1, q)
        Case "TRM"
            SetCellValue linha, 2, matrizAtributos(1, q)
        Case "NO_ESTRU"
            SetCellValue linha, 5, matrizAtributos(1, q)
        Case "I_COORD_N"
            SetCellValue linha, 10, matrizAtributos(1, q)
        Case "I_COORD_E"
            SetCellValue linha, 11, matrizAtributos(1, q)
        Case "F_COORD_N"
            SetCellValue linha, 12, matrizAtributos(1, q)
        Case "F_COORD_E"
            SetCellValue linha, 13, matrizAtributos(1, q)
        Case "QE"
            SetCellValue linha, 9, matrizAtributos(1, q)
    End Select
Next q
End Sub
Sub RegistraTrmNoPonto(trm As String, coluna As Integer, linha As Integer)
    SetCellValue linha, coluna, trm
End Sub

Attribute VB_Name = "mdl_Importacao"
Global matrizDadosExcel() As String
Global qtdColunaMatrizExcel As Integer

Sub ObterDadosDaPlanilha(linha As Integer, colunas As Integer)
Dim q As Integer
qtdColunaMatrizExcel = 0

Erase matrizDadosExcel 'Zerando matriz
ReDim Preserve matrizDadosExcel(1, colunas - 1)

 For q = 0 To colunas - 1
    matrizDadosExcel(0, q) = GetCellValue(1, q + 1)
    matrizDadosExcel(1, q) = GetCellValue(linha, q + 1)
        
       Select Case matrizDadosExcel(0, q)
        Case "NÚMERO DA QUADRA"
            matrizDadosExcel(0, q) = "QE"
        Case "COTA DO TERRENO"
            matrizDadosExcel(0, q) = "COTAT"
        Case "COTA DE FUNDO"
            matrizDadosExcel(0, q) = "COTAF"
        Case "PROFUNDIDADE"
            matrizDadosExcel(0, q) = "PROFPV"
        Case "PROFUNDIDADE A JUSANTE"
            matrizDadosExcel(0, q) = "PROF2"
        Case "DIÂMETRO"
            matrizDadosExcel(0, q) = "DIAM"
        Case "DECLIVIDADE"
            matrizDadosExcel(0, q) = "DECLIVIDADE"
        Case "ORGÃO ACESSÓRIO"
             matrizDadosExcel(0, q) = "NO_ESTRU"
    End Select
    qtdColunaMatrizExcel = qtdColunaMatrizExcel + 1
 Next q
End Sub
Function ColocarDadosNoBloco(oBlk As AcadBlockReference) As String
Dim count As Integer
Dim i As Integer
Dim z As Integer
Dim varAttribs As Variant

    If oBlk.HasAttributes Then
        varAttribs = oBlk.GetAttributes
        For i = 0 To qtdColunaMatrizExcel - 1
            For z = LBound(varAttribs) To UBound(varAttribs)
                If matrizDadosExcel(0, i) = varAttribs(z).TagString Then
                   varAttribs(z).TextString = matrizDadosExcel(1, i)
                End If
             Next z
        Next
    End If
End Function
Function ObterBlocosPeloId(id As LongLong) As AcadBlockReference
Dim elem As Object
Dim oBlk As AcadBlockReference
Dim objCadEntity As AcadEntity
Dim count As Integer
Dim oSelect As AcadSelectionSet
Dim iFilterCode(0) As Integer
Dim vFilterValue(0) As Variant
Dim intI As Integer
Dim intLin As Integer


    For Each objCadEntity In ActiveDocument.ModelSpace
        If TypeOf objCadEntity Is AcadBlockReference Then
            Set oBlk = objCadEntity
            If oBlk.HasAttributes Then
                If oBlk.ObjectID = id Then
                    Set ObterBlocosPeloId = oBlk
                    Exit Function
                End If
            End If
        End If
    Next
End Function

Attribute VB_Name = "mdl_OpenFile"
Option Explicit
'Vba6    True    Visual Basic for Applications, version 6.0 compatible.
'Vba6    False   not Visual Basic for Applications, version 6.0 compatible.
'Vba7    True    Visual Basic for Applications, version 7.0 compatible.
'Vba7    False   not Visual Basic for Applications, version 7.0 compatible.
'Win16   False   Indicates development environment is not 16-bit compatible.
'Win32   True    32-bit compatible.
'Win64   True    64-bit compatible.

#If Win64 Then
Private Declare PtrSafe Function GetOpenFileName Lib "comdlg32.dll" _
    Alias "GetOpenFileNameA" (OFN As OPENFILENAME) As Boolean
    
Private Declare PtrSafe Function GetVersionExA Lib "kernel32" _
    (lpVersionInformation As OSVERSIONINFO) As Integer
Private Type OPENFILENAME
  lStructSize As Long
  hwndOwner As LongPtr
  hInstance As LongPtr
  lpstrFilter As String
  lpstrCustomFilter As String
  nMaxCustFilter As Long
  nFilterIndex As Long
  lpstrFile As String
  nMaxFile As Long
  lpstrFileTitle As String
  nMaxFileTitle As Long
  lpstrInitialDir As String
  lpstrTitle As String
  flags As Long
  nFileOffset As Integer
  nFileExtension As Integer
  lpstrDefExt As String
  lCustData As Long
  lpfnHook As LongPtr
  lpTemplateName As String
End Type

Private Type OSVERSIONINFO
  dwOSVersionInfoSize As Long
  dwMajorVersion As Long
  dwMinorVersion As Long
  dwBuildNumber As Long
  dwPlatformId As Long
  szCSDVersion As String * 128
End Type

#ElseIf Win32 Then
Private Declare PtrSafe Function GetOpenFileName Lib "comdlg32.dll" Alias "GetOpenFileNameA" (OFN As OPENFILENAME) As Boolean
Private Declare PtrSafe Function GetVersionExA Lib "kernel32" (lpVersionInformation As OSVERSIONINFO) As Integer

Private Type OPENFILENAME
  lStructSize As Long
  hwndOwner As Long
  hInstance As Long
  lpstrFilter As String
  lpstrCustomFilter As String
  nMaxCustFilter As Long
  nFilterIndex As Long
  lpstrFile As String
  nMaxFile As Long
  lpstrFileTitle As String
  nMaxFileTitle As Long
  lpstrInitialDir As String
  lpstrTitle As String
  flags As Long
  nFileOffset As Integer
  nFileExtension As Integer
  lpstrDefExt As String
  lCustData As Long
  lpfnHook As Long
  lpTemplateName As String
End Type

Private Type OSVERSIONINFO
  dwOSVersionInfoSize As Long
  dwMajorVersion As Long
  dwMinorVersion As Long
  dwBuildNumber As Long
  dwPlatformId As Long
  szCSDVersion As String * 128
End Type
#End If
Private Sub UserForm_Activate()
#If VBA7 Then

#Else
MsgBox "Only Autocad 2014 allowed"
End
#End If
End Sub
Public Function getVersion() As String
  Dim osinfo As OSVERSIONINFO
  Dim retvalue As Integer
  Dim Wver As String
  Dim Vname As String
 
  osinfo.dwOSVersionInfoSize = 148
  osinfo.szCSDVersion = VBA.Space$(128)
  retvalue = GetVersionExA(osinfo)

  Wver = osinfo.dwMajorVersion & "." & osinfo.dwMinorVersion

Select Case Wver
Case "6.2": Vname = "Windows 8"
'Case "6.2": Vname = "Windows Server 2012"
Case "6.1": Vname = "Windows 7"
'Case "6.1": Vname = "Windows Server 2008 R2"
Case "6.0": Vname = "Windows Server 2008"
'Case "6.0": Vname = "Windows Vista"
'Case "5.2": Vname = "Windows Server 2003 R2"
'Case "5.2": Vname = "Windows Home Server"
Case "5.2": Vname = "Windows Server 2003"
'Case "5.2": Vname = "Windows XP Professional x64 Edition"
Case "5.1": Vname = "Windows XP"
Case "5.0": Vname = "Windows 2000"
End Select

'getVersion = Wver + "_" + Vname
getVersion = Vname
End Function
Public Sub FindFile(ByRef Filepath As String, sFilter As String, ByRef cancelled As Boolean)
    Dim OpenFile As OPENFILENAME
    Dim lReturn As Long
    
    OpenFile.lStructSize = LenB(OpenFile)

    '// "Text Files (*.txt)" & Chr$(0) & "*.sky" & Chr$(0) & "All Files (*.*)" & Chr$(0) & "*.*"
    'sFilter = "Excel Files (*.xl*)" & Chr(0) & "*.xl*"
    
    OpenFile.lpstrFilter = sFilter
    OpenFile.nFilterIndex = 1
    OpenFile.lpstrFile = VBA.String(257, 0)
    OpenFile.nMaxFile = Len(OpenFile.lpstrFile) - 1
    OpenFile.lpstrFileTitle = OpenFile.lpstrFile
    OpenFile.nMaxFileTitle = OpenFile.nMaxFile
    'OpenFile.lpstrInitialDir = Application.ActiveDocument.path
    If Filepath > "" Then
       OpenFile.lpstrInitialDir = Filepath
    Else
       OpenFile.lpstrInitialDir = "C:\"
    End If
    
    OpenFile.lpstrTitle = "Find " + sFilter
    OpenFile.flags = 0
    lReturn = GetOpenFileName(OpenFile)
    
    If lReturn = 0 Then
       cancelled = True
       Filepath = vbNullString
    Else
      cancelled = False
      Filepath = VBA.Trim(OpenFile.lpstrFile)
      Filepath = Replace(Filepath, VBA.Chr(0), vbNullString)
    End If

    Exit Sub
    
errTrap:
    Exit Sub
    Resume

End Sub
Public Function getFiled(sPath As String, sExt As String, sDescr As String) As String
  Dim bCancelled As Boolean
  Dim ftype As String
  ftype = sDescr + " (*." + sExt + ")" + VBA.Chr(0) + "*." + sExt
  FindFile sPath, ftype, bCancelled
  If bCancelled Then getFiled = "" Else getFiled = sPath
End Function
Private Sub TestEnvionment_Click()
Dim A$
#If Win64 Then
   A$ = A$ + "Win64=True" + vbCrLf
#Else
   A$ = A$ + "Win64=False" + vbCrLf
#End If

#If Win32 Then
   A$ = A$ + "Win32=True" + vbCrLf
#Else
   A$ = A$ + "Win32=False" + vbCrLf
#End If

#If Win16 Then
   A$ = A$ + "Win16=True" + vbCrLf
#Else
   A$ = A$ + "Win16=False" + vbCrLf
#End If

#If VBA6 Then
   A$ = A$ + "Vba6=True" + vbCrLf
#Else
   A$ = A$ + "Vba6=False" + vbCrLf
#End If

#If VBA7 Then
   A$ = A$ + "Vba7=True" + vbCrLf
#Else
   A$ = A$ + "Vba7=False" + vbCrLf
#End If

MsgBox A$

Dim Vrstica As Variant
Vrstica = Split(Application.Path, "\")
Dim hostName As String
hostName = VBA.Environ$("computername")
Dim acadVer As String
acadVer = Vrstica(UBound(Vrstica))

Dim WinVersion As String
WinVersion = getVersion

Open ThisDrawing.Path + "\Env " + WinVersion + " " + hostName + " " + acadVer + ".txt" For Output As #1
Print #1, ThisDrawing.FullName
Print #1, Application.FullName
Print #1, A$
Close #1


End Sub

Attribute VB_Name = "mdl_Util"
Public Sub TRA()
frmColetor.show
End Sub
Public Sub DDD()
frmExportarImportarDados.show
End Sub
Public Sub UTFesg()
frmMenu.show
End Sub
Function EncontrarBlocoPeloTextAtributo(strColetorETramo As String) As AcadBlockReference
Dim elem As Object
Dim oBlk As AcadBlockReference
Dim item As Object
Dim Array1 As Variant
Dim count As Integer
Dim MBtest1 As String
Dim str As String
Dim oSelect As AcadSelectionSet
Dim iFilterCode(0) As Integer
Dim vFilterValue(0) As Variant
Dim varAttribs As Variant
Dim intI As Integer
Dim i As Integer

    iFilterCode(0) = 0
    vFilterValue(0) = "INSERT"

    'Excluir Seleções anteriores
    On Error Resume Next
    For i = 0 To ActiveDocument.SelectionSets.count - 1
        If ActiveDocument.SelectionSets.item(i).Name = "EncontrarBlocoPeloAtributo" Then
            ActiveDocument.SelectionSets.item(i).Delete
        End If
    Next i
    'Obter todas os bloco insert
    Set oSelect = ActiveDocument.SelectionSets.Add("EncontrarBlocoPeloAtributo")
    oSelect.Select acSelectionSetAll, , , iFilterCode, vFilterValue
    
    'Obter bloco com atributo x
    For Each elem In oSelect
        If elem.EntityName = "AcDbBlockReference" Then
            If elem.HasAttributes Then
                Set oBlk = elem
                varAttribs = oBlk.GetAttributes
                For intI = LBound(varAttribs) To UBound(varAttribs)
                    'Debug.Print varAttribs(intI).TagString
                    If varAttribs(intI).TextString = strColetorETramo Then
                        Set EncontrarBlocoPeloTextAtributo = oBlk
                        Exit Function
                    End If
                Next
            End If
        End If
    Next

End Function
Sub ZoomObjeto(objZoom As AcadEntity)
    Dim minP1 As Variant, maxP1 As Variant
    
    objZoom.GetBoundingBox minP1, maxP1
    ActiveDocument.Application.ZoomCenter minP1, 200
    Exit Sub
End Sub
Sub ZoomTotalObjeto(objZoom As AcadEntity)
    Dim minP1 As Variant, maxP1 As Variant
    On Error GoTo ZoomObjeto_Err
    
    objZoom.GetBoundingBox minP1, maxP1
    ActiveDocument.Application.ZoomWindow minP1, maxP1
    'ActiveDocument.Application.ZoomCenter minP1, 7.5
    Exit Sub
ZoomObjeto_Err:
End Sub
Public Function DistancePoint(firstPoint As Variant, endPoint As Variant) As Double
    Dim dXSide As Double
    Dim dYSide As Double
    Dim dFirstPoint(2) As Double
    Dim dendpoint(2) As Double
    Dim dDist As Double
    
    dFirstPoint(0) = firstPoint(0)
    dFirstPoint(1) = firstPoint(1)
    
    dendpoint(0) = endPoint(0)
    dendpoint(1) = endPoint(1)
    
    If dFirstPoint(0) > dendpoint(0) Then
        dXSide = dFirstPoint(0) - dendpoint(0)
    Else
        dXSide = dendpoint(0) - dFirstPoint(0)
    End If
    
    If dFirstPoint(1) > dendpoint(1) Then
        dYSide = dFirstPoint(1) - dendpoint(1)
    Else
        dYSide = dendpoint(1) - dFirstPoint(1)
    End If
    
    dDist = Sqr(SQ(dXSide) + SQ(dYSide))
    
    DistancePoint = dDist
End Function

Private Function SQ(Number As Double) As Double
    SQ = Number * Number
End Function


Public Sub ModifyProperty(prop As String, value As Double, bobj As AcadBlockReference)
Dim dybprop As Variant, i As Integer

    If bobj.ObjectName = "AcDbBlockReference" Then
        If bobj.IsDynamicBlock Then
            dybprop = bobj.GetDynamicBlockProperties
            For i = LBound(dybprop) To UBound(dybprop)
                If dybprop(i).PropertyName = prop Then
                    dybprop(i).value = value
                End If
            Next i
        End If
    End If
End Sub
Function RetornaParteDeUmaString(strPalavra As String, strCaracterCorta As String, blnDaEsquerda As Boolean) As String
      Dim intCount As Integer
      Dim i As Integer
      Dim strNovaPalavra As String
      Dim strLetra As String

     On Error GoTo fnRetornaParteDeUmaString_Error

    intCount = Len(strPalavra) 'obtém o numero de letras
      'verifica toda a palavra até achar o caracter x
    For i = 0 To intCount
     strLetra = Mid(strPalavra, intCount - i, 1)
        If strLetra = strCaracterCorta Then
            If blnDaEsquerda = False Then
                strNovaPalavra = Mid(strPalavra, intCount - i, intCount)
            Else
                strNovaPalavra = Mid(strPalavra, 1, intCount - i)
           End If
           Exit For
       End If
   Next i
      'Retorna a palavra quebrada(sigla)
   RetornaParteDeUmaString = strNovaPalavra

     Exit Function

fnRetornaParteDeUmaString_Error:
     Err.Clear
     Resume Next
     Exit Function
End Function
Function TramoExiste(strColetorETramo As String) As Boolean
Dim elem As Object
Dim oBlk As AcadBlockReference
Dim item As Object
Dim Array1 As Variant
Dim count As Integer
Dim MBtest1 As String
Dim str As String
Dim oSelect As AcadSelectionSet
Dim iFilterCode(0) As Integer
Dim vFilterValue(0) As Variant
Dim varAttribs As Variant
Dim intI As Integer
Dim i As Integer

    iFilterCode(0) = 0
    vFilterValue(0) = "INSERT"

    'Excluir Seleções anteriores
    On Error Resume Next
    For i = 0 To ActiveDocument.SelectionSets.count - 1
        If ActiveDocument.SelectionSets.item(i).Name = "EncontrarBlocoPeloAtributo" Then
            ActiveDocument.SelectionSets.item(i).Delete
        End If
    Next i
    'Obter todas os bloco insert
    Set oSelect = ActiveDocument.SelectionSets.Add("EncontrarBlocoPeloAtributo")
    oSelect.Select acSelectionSetAll, , , iFilterCode, vFilterValue
    
    'Obter bloco com atributo x
    For Each elem In oSelect
        If elem.EntityName = "AcDbBlockReference" Then
            If elem.HasAttributes Then
                Set oBlk = elem
                varAttribs = oBlk.GetAttributes
                For intI = LBound(varAttribs) To UBound(varAttribs)
                    'Debug.Print varAttribs(intI).TagString
                    If varAttribs(intI).TextString = strColetorETramo Then
                        TramoExiste = True
                        Exit Function
                    End If
                Next
            End If
        End If
    Next
TramoExiste = False
End Function
Public Function BubbleSrt(ArrayIn, Ascending As Boolean)

Dim SrtTemp As Variant
Dim i As Long
Dim j As Long


If Ascending = True Then
    For i = LBound(ArrayIn) To UBound(ArrayIn)
         For j = i + 1 To UBound(ArrayIn)
             If ArrayIn(i) > ArrayIn(j) Then
                 SrtTemp = ArrayIn(j)
                 ArrayIn(j) = ArrayIn(i)
                 ArrayIn(i) = SrtTemp
             End If
         Next j
     Next i
Else
    For i = LBound(ArrayIn) To UBound(ArrayIn)
         For j = i + 1 To UBound(ArrayIn)
             If ArrayIn(i) < ArrayIn(j) Then
                 SrtTemp = ArrayIn(j)
                 ArrayIn(j) = ArrayIn(i)
                 ArrayIn(i) = SrtTemp
             End If
         Next j
     Next i
End If

BubbleSrt = ArrayIn

End Function
